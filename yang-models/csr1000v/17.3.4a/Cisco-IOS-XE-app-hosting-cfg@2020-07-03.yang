module Cisco-IOS-XE-app-hosting-cfg {
  yang-version 1;
  namespace "http://cisco.com/ns/yang/Cisco-IOS-XE-app-hosting-cfg";
  prefix app-hosting-ios-xe-cfg;

  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for app-hosting configuration data.
     Copyright (c) 2019-2020 by Cisco Systems, Inc.
     All rights reserved.";

  revision 2020-07-03 {
    description
      "- Added support for docker package runtime options";
    reference "2.3.17030(m)";
    cisco-semver:module-version "2.3.17030(m)";
  }
  revision 2020-03-01 {
    description
      "- Suppress app-hosting dynamic resources";
    reference "2.3.1";
    cisco-semver:module-version "2.3.1";
  }
  revision 2019-11-01 {
    description
      "- Add app-hosting dynamic resources
       - Add support for mac-forwarding and mirroring on guest interface
       - Add support for assigning usb-port label";
    reference "2.3.0";
    cisco-semver:module-version "2.3.0";
  }
  revision 2019-06-11 {
    description
      "- Add support for Device USB information
       - Add docker run-time options
       - Rename disk size parameter and change description
       - Added semantic version
       - Add support for access guest interface number";
    reference "2.2.0";
    cisco-semver:module-version "2.2.0";
  }
  revision 2019-01-11 {
    description
      "- Adding KR port interface configuration in app-hosting
       - Cleaned up spelling errors in descriptions
       - Add start
       - Rename the KR port to App Interface
       - Add a new leaf to remove the app interface mode setting";
    reference "2.1.0";
    cisco-semver:module-version "2.1.0";
  }
  revision 2018-06-14 {
    description
      "Rename virtual service to app-hosting";
    reference "2.0.0";
    cisco-semver:module-version "2.0.0";
  }
  revision 2018-01-01 {
    description
      "Initial revision";
    reference "1.0.0";
    cisco-semver:module-version "1.0.0";
  }

  typedef im-app-appintf-mode {
    type enumeration {
      enum "appintf-not-set" {
        value 0;
        description
          "App interface port is not set";
      }
      enum "appintf-trunk" {
        value 1;
        description
          "App interface port configure for trunk mode";
      }
      enum "appintf-vlan" {
        value 2;
        description
          "App interface port configuration for VLAN access mode";
      }
      enum "appintf-access" {
        value 3;
        description
          "App interface port configuration for access mode";
      }
    }
    description
      "App interface mode type";
  }

  grouping im-app-resource {
    description
      "Application Resource information";
    leaf profile-name {
      type string {
        length "0..64";
        pattern "[0-9a-zA-Z\\-_]*";
      }
      default "";
      description
        "Resource profile name";
    }
    leaf vcpu {
      type uint16;
      must "../vcpu <= 65535" {
        error-message "must be <= 65535";
        error-app-tag "must-violation";
      }
      description
        "Amount of VCPUs allocated for the application";
    }
    leaf cpu-units {
      type uint16 {
        range "0 .. 20000";
      }
      must "../cpu-units <= 20000" {
        error-message "must be <= 20000";
        error-app-tag "must-violation";
      }
      default "0";
      description
        "Amount of reserved cpu in unit";
    }
    leaf memory-capacity-mb {
      type uint16 {
        range "0 .. 4096";
      }
      must "../memory-capacity-mb <= 4096" {
        error-message "must be <= 4096";
        error-app-tag "must-violation";
      }
      default "0";
      description
        "Amount of reserved memory in MB";
    }
    leaf disk-size-mb {
      type uint16 {
        range "0 .. 8192";
      }
      must "../disk-size-mb <= 8192" {
        error-message "must be <= 8192";
        error-app-tag "must-violation";
      }
      default "0";
      description
        "IOX Application persistent disk size in MB";
    }
    leaf pkg-profile-name {
      type string {
        length "0..64";
        pattern "[0-9a-zA-Z\\-_]*";
      }
      description
        "Resource package profile name";
    }
  }

  grouping im-app-docker-run-opts {
    description
      "Multi-line docker run-time options";
    leaf line-index {
      type uint16 {
        range "1 .. 30";
      }
      description
        "Index number";
    }
    leaf line-run-opts {
      type string {
        length "0..235";
      }
      description
        "Docker run-time options";
    }
  }

  grouping im-app-device {
    description
      "Application device information";
    leaf device-name {
      type string {
        length "0..32";
        pattern "[0-9a-zA-Z]*";
      }
      default "";
      description
        "device name";
    }
  }

  grouping im-app-mac {
    description
      "Application MAC information";
    leaf mac-address {
      type yang:mac-address;
      description
        "MAC address";
    }
    leaf mac-interface-name {
      type string {
        length "0..32";
        pattern "[0-9a-zA-Z]*";
      }
      default "";
      description
        "MAC interface name";
    }
  }

  grouping im-app-network {
    description
      "Application Network information";
    leaf vnic-gateway-0 {
      type string {
        length "1..2";
        pattern "[0-9]*";
      }
      description
        "Vnic gateway";
    }
    leaf virtualportgroup-guest-interface-name-1 {
      type string {
        length "1";
        pattern "[0-3]*";
      }
      description
        "VirtualPortGroup guest interface name as number in range of 0 .. 3";
    }
    leaf virtualportgroup-guest-ip-address-1 {
      type inet:ip-address;
      description
        "Guest interface IP address";
    }
    leaf virtualportgroup-guest-ip-netmask-1 {
      type inet:ip-address;
      description
        "Guest IP netmask";
    }
    leaf virtualportgroup-application-default-gateway-1 {
      type inet:ip-address;
      description
        "VirtualPortGroup application default gateway IP address";
    }
    leaf nameserver-0 {
      type inet:ip-address;
      description
        "Name server IP address";
    }
    leaf virtualportgroup-guest-interface-default-gateway-1 {
      type uint8;
      must "../virtualportgroup-guest-interface-default-gateway-1 <= 3" {
        error-message "must be <= 3";
        error-app-tag "must-violation";
      }
      description
        "VirtualPortGroup default gateway guest interface";
    }
    leaf vnic-gateway-1 {
      type string {
        length "1..2";
        pattern "[0-9]*";
      }
      description
        "Vnic gateway";
    }
    leaf virtualportgroup-guest-interface-name-2 {
      type string {
        length "1";
        pattern "[0-3]*";
      }
      description
        "VirtualPortGroup guest interface name as number in range of 0 .. 3";
    }
    leaf virtualportgroup-guest-ip-address-2 {
      type inet:ip-address;
      description
        "Guest interface IP address";
    }
    leaf virtualportgroup-guest-ip-netmask-2 {
      type inet:ip-address;
      description
        "Guest IP netmask";
    }
    leaf virtualportgroup-application-gateway-2 {
      type inet:ip-address;
      description
        "VirtualPortGroup application gateway IP address";
    }
    leaf nameserver-1 {
      type inet:ip-address;
      description
        "Name server IP address";
    }
    leaf virtualportgroup-guest-interface-default-gateway-2 {
      type uint8;
      must "../virtualportgroup-guest-interface-default-gateway-2 <= 1 " {
        error-message "must be <= 1";
        error-app-tag "must-violation";
      }
      description
        "VirtualPortGroup default gateway guest interface";
    }
    leaf vnic-gateway-2 {
      type string {
        length "1..2";
        pattern "[0-9]*";
      }
      description
        "Vnic gateway";
    }
    leaf virtualportgroup-guest-interface-name-3 {
      type string {
        length "1";
        pattern "[0-3]*";
      }
      description
        "VirtualPortGroup guest interface name as number in range of 0 .. 3";
    }
    leaf virtualportgroup-guest-ip-address-3 {
      type inet:ip-address;
      description
        "Guest interface IP address";
    }
    leaf virtualportgroup-guest-ip-netmask-3 {
      type inet:ip-address;
      description
        "Guest IP netmask";
    }
    leaf virtualportgroup-application-gateway-3 {
      type inet:ip-address;
      description
        "VirtualPortGroup application gateway IP address";
    }
    leaf nameserver2 {
      type inet:ip-address;
      description
        "Name server IP address";
    }
    leaf virtualportgroup-guest-interface-default-gateway-3 {
      type uint8;
      must "../virtualportgroup-guest-interface-default-gateway-3 <= 1" {
        error-message "must be <= 1";
        error-app-tag "must-violation";
      }
      description
        "VirtualPortGroup default gateway guest interface";
    }
    leaf vnic-gateway-3 {
      type string {
        length "1..2";
        pattern "[0-9]*";
      }
      description
        "Vnic gateway";
    }
    leaf virtualportgroup-guest-interface-name-4 {
      type string {
        length "1";
        pattern "[0-3]*";
      }
      description
        "VirtualPortGroup guest interface name as number in range of 0 .. 3";
    }
    leaf virtualportgroup-guest-ip-address-4 {
      type inet:ip-address;
      description
        "Guest interface IP address";
    }
    leaf virtualportgroup-guest-ip-netmask-4 {
      type inet:ip-address;
      description
        "Guest IP netmask";
    }
    leaf virtualportgroup-application-gateway-4 {
      type inet:ip-address;
      description
        "VirtualPortGroup application gateway IP address";
    }
    leaf nameserver-3 {
      type inet:ip-address;
      description
        "Name server IP address";
    }
    leaf virtualportgroup-guest-interface-default-gateway-4 {
      type uint8;
      must "../virtualportgroup-guest-interface-default-gateway-4 <= 1" {
        error-message "must be <= 1";
        error-app-tag "must-violation";
      }
      description
        "VirtualPortGroup default gateway guest interface";
    }
    leaf management-interface-name {
      type string {
        length "1";
        pattern "[0-3]*";
      }
      description
        "Management port guest interface name as number in range of 0 .. 3";
    }
    leaf management-guest-ip-address {
      type inet:ip-address;
      description
        "Guest management port interface IP address";
    }
    leaf management-guest-ip-netmask {
      type inet:ip-address;
      description
        "Guest management port interface IP netmask";
    }
    leaf management-application-gateway {
      type inet:ip-address;
      description
        "Management port application gateway IP address";
    }
    leaf nameseerver4 {
      type inet:ip-address;
      description
        "Name server IP address";
    }
    leaf management-guest-interface-default-gateway {
      type uint8;
      must "../management-guest-interface-default-gateway <= 1" {
        error-message "must be <= 1";
        error-app-tag "must-violation";
      }
      description
        "Management port default gateway guest interface";
    }
    container application-mac-address {
      description
        "Application MAC address";
      uses app-hosting-ios-xe-cfg:im-app-mac;
    }
    leaf appintf-guest-interface-number {
      type uint8;
      must "../appintf-guest-interface-number <= 63" {
        error-message "Guest interface must be in range of 0..63";
        error-app-tag "must-violation";
      }
      description
        "Guest interface port number for trunk mode in range of 0..63";
    }
    leaf appintf-vlan-mode {
      type app-hosting-ios-xe-cfg:im-app-appintf-mode;
      default "appintf-not-set";
      description
        "App interface mode configuration";
    }
    leaf appintf-access-interface-number {
      type uint8;
      must "../appintf-access-interface-number <= 63" {
        error-message "Access interface must be in range of 0..63";
        error-app-tag "must-violation";
      }
      description
        "Guest interface port number for access mode in range of 0..63";
    }
    leaf mac-forward-enable {
      type boolean;
      default "false";
      description
        "Enable or Disable MAC forwarding mode on bridge";
    }
    leaf mirror-enable {
      type boolean;
      default "false";
      description
        "Enable or Disable Mirroring mode on bridge";
    }
  }

  grouping application-im-app-intf-vlan-rule {
    description
      "App interface VLAN access to guest interface table mapping";
    leaf vlan-id {
      type uint16;
      must "(../vlan-id >= 1 and ../vlan-id <= 4094)" {
        error-message "VLAN ID must be in range of 1..4094";
        error-app-tag "must-violation";
      }
      description
        "VLAN ID in range of 1..4094";
    }
    leaf guest-interface {
      type uint8;
      must "../guest-interface <= 63" {
        error-message "Guest interface must be in range of 0..63";
        error-app-tag "must-violation";
      }
      description
        "Guest interface number in range of 0..63";
    }
    leaf guest-ip {
      type inet:ip-address;
      description
        "Guest interface IP address";
    }
    leaf guest-ipnetmask {
      type inet:ip-address;
      description
        "Guest IP netmask";
    }
    leaf mac-forward-enable {
      type boolean;
      default "false";
      description
        "Enable or Disable MAC forwarding mode on bridge";
    }
    leaf mirror-enable {
      type boolean;
      default "false";
      description
        "Enable or Disable Mirroring mode on bridge";
    }
  }

  grouping application-im-app-device-usb {
    description
      "App device details";
    leaf usb-port-num {
      type uint16;
      description
        "USB port number";
    }
    leaf usb-port-label {
      type string {
        length "0..63";
        pattern "[0-9a-zA-Z_]*";
      }
      description
        "USB port label";
    }
  }

  grouping application-information {
    description
      "Application Information";
    leaf application-name {
      type string {
        length "1..40";
        pattern "[0-9a-zA-Z_]*";
      }
      description
        "Application name";
    }
    container application-network-resource {
      description
        "Application Network Resource Information";
      uses app-hosting-ios-xe-cfg:im-app-network;
    }
    container application-resource-profile {
      description
        "Application Resource profile";
      uses app-hosting-ios-xe-cfg:im-app-resource;
    }
    container application-attached-device {
      description
        "Application attached device";
      uses app-hosting-ios-xe-cfg:im-app-device;
    }
    container appintf-vlan-rules {
      description
        "App interface rules for VLAN access mode";
      list appintf-vlan-rule {
        key "vlan-id";
        description
          "List of App interface rules for VLAN access mode";
        uses app-hosting-ios-xe-cfg:application-im-app-intf-vlan-rule;
      }
    }
    leaf start {
      type boolean;
      description
        "Application run state";
    }
    container dev-usbs {
      description
        "Device USB details for this app";
      list dev-usb {
        key "usb-port-num";
        description
          "List of USB ports that are associated with this app";
        uses app-hosting-ios-xe-cfg:application-im-app-device-usb;
      }
    }
    leaf docker-resource {
      type boolean;
      default "false";
      description
        "Enable or Disable docker resources";
    }
    container run-optss {
      description
        "List of docker run-time options";
      list run-opts {
        key "line-index";
        description
          "Docker run-time options";
        uses app-hosting-ios-xe-cfg:im-app-docker-run-opts;
      }
    }
    leaf prepend-pkg-opts {
      type boolean;
      description
        "Add docker runtime options specified in the app package file to the beginning of the docker runtime option";
    }
  }

  grouping application-hosting-infra-record {
    description
      "Application hosting Infra Record";
    leaf application-hosting-infra-enable-statue {
      type uint8;
      must "../application-hosting-infra-enable-statue <= 1" {
        error-message "must be <= 1";
        error-app-tag "must-violation";
      }
      default "0";
      description
        "Application hosting Infra enable status";
    }
    leaf sign-verification {
      type boolean;
      description
        "Signature verification of all applications";
    }
  }

  container app-hosting-cfg-data {
    description
      "app-hosting configuration data";
    container apps {
      description
        "Application list";
      list app {
        key "application-name";
        description
          "Application info";
        uses app-hosting-ios-xe-cfg:application-information;
      }
    }
    container controls {
      presence "Controls";
      description
        "App-hosting control";
      uses app-hosting-ios-xe-cfg:application-hosting-infra-record;
    }
  }
}
